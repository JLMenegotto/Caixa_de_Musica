(defun Cx:Listar_os_layers (/ layer)
                                            (setq  layer (tblsearch "LAYER" "0" t))

                                            (while layer
					                (if (< 0 (Cx:dxf 62 layer))
					                    (Cx:Adiciona_layer  layer)
							)
					                (setq layer  (tblnext "LAYER"))
                                            )
                                            (setq *rtm_O_layers*  (reverse  *rtm_O_layers*))
                                            (setq *rtm_O_vozes*   (list
								        (list "0" (car *rtm_O_layers*) "0")
								        (list "1" (car *rtm_O_layers*) "0")
								        (list "2" (car *rtm_O_layers*) "0")
								        (list "3" (car *rtm_O_layers*) "0")
								        (list "4" (car *rtm_O_layers*) "0")
								        (list "5" (car *rtm_O_layers*) "0")
                                                                        (list "6" (car *rtm_O_layers*) "0")
                                                                        (list "7" (car *rtm_O_layers*) "0")
								        (list "8" (car *rtm_O_layers*) "0")
								        (list "9" (car *rtm_O_layers*) "0")
			                                          )
				            )
)

(defun Cx:Adiciona_layer (#lay /  layer_candidato)
                                         (setq layer_candidato  (Cx:dxf 2 #lay))
                                         (cond
					        ((Cx:Habilita_Layer? layer_candidato)
                                                     (setq *rtm_O_layers*  (cons layer_candidato  *rtm_O_layers*))
						)
					 )
)

(defun Cx:Habilita_Layer? (#la)
                                         (and
                                                  (/= "0"          (strcase #la))
					          (/= "PTS_NORMAL" (strcase #la))
						  (/= "PTS_INVERT" (strcase #la))
						  (/= "PTS_SILENC" (strcase #la))
						  (/= "EGC-TUBO"   (strcase #la))
						  (/= "ASHADE"     (strcase #la))
						  (/= "CAIXAM"     (strcase #la))
				         )
)

(defun Cx:coloca_no_layer (#lay)
                                         (command "._chprop" (entlast) "" "_la"  #lay  "")
)

(defun Cx:addlayer (#l / obj-l)
                                         (Cx:eco_of)
                	                 (cond
               	                               ((not (tblsearch "LAYER" (nth 0 #l)))		   
               			                     (setq obj-l (vla-add *rtm_lays* (nth 0 #l)))
               			               )
               		                 )                                      
                                         (command "._layer" "_C" (nth 1 #l) (nth 0 #l) "")
                                         (Cx:eco_on)
)
