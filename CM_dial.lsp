(defun Cx:Activa_dialogo ()
                             (setq qdialogo (load_dialog  *rtm_ar_DCL*))
                             (new_dialog  *rtm_di_DCL*  qdialogo)  
   (Cx:error "dial_01")
                             (Cx:campos '(*rtm_NomeOpus*) '("OPUS") '("Opus_01"))

                             (mapcar '(lambda (voz) (set (read (strcat "*rtm_escala_"  voz "*"))     (Cx:pega_escala              "0"))) *rtm_vozes*)
                             (mapcar '(lambda (voz) (set (read (strcat "*rtm_escala_"  voz "_txt*")) (Cx:pega_escala_txt          "0"))) *rtm_vozes*)
                             (mapcar '(lambda (voz) (set (read (strcat "*metodo_Voz_0" voz "*"))     (Cx:Metodo_da_voz (atoi voz) "0"))) *rtm_vozes*)
   (Cx:error "dial_02")
                             (Cx:activa_vozes   *rtm_O_vozes*)     (Cx:error "dial_03")
                             (Cx:activa_Layers  *rtm_O_layers*)    (Cx:error "dial_04")
                             (Cx:activa_coro    *rtm_L_instru*)    (Cx:error "dial_05")
                             (Cx:activa_escala  *rtm_escalas*)     (Cx:error "dial_06")
                             (Cx:activa_Tempos  *rtm_tempo_vozes*) (Cx:error "dial_07")
                             (Cx:activa_Metodos (Cx:metodos))      (Cx:error "dial_08")
         
                             (mapcar '(lambda (voz) (set_tile (strcat "Voz_0"     voz) "0")) *rtm_vozes*) (Cx:error "dial_09")
                             (mapcar '(lambda (voz) (set_tile (strcat "Pts_Nor_0" voz) "1")) *rtm_vozes*) (Cx:error "dial_10")
  (Cx:error "dial_11")
                             (set_tile    "PULSOS"       *rtm_pulsos*)
                             (set_tile    "TXTPULSOS"    *rtm_pulsos*)
                             (set_tile    "UNIDADE"      (rtos *rtm_unidad*  2  8))
                             (set_tile    "PERIODO"      (Cx:string  *rtm_periodo*))
                             (set_tile    "FRASE"        (Cx:string  *rtm_M_Frase*))
  (Cx:error "dial_12")
                             (set_tile    "Regla_01"   "0")
                             (set_tile    "Regla_02"   "0")  
                             (set_tile    "Regla_03"   "0")
                             (set_tile    "Regla_04"   "0")
                             (set_tile    "Regla_05"   "1")
                             (set_tile    "Regla_06"   "0")
                             (set_tile    "Regla_07"   "0")
                             (set_tile    "Regla_08"   "0")
                             (set_tile    "Regla_09"   "0")       
                             (set_tile    "Desloca"    "5")
                             (set_tile    "DinamicaX"  "3")
                             (set_tile    "DinamicaY"  "6")
                             (set_tile    "DinamicaZ"  "9")
  (Cx:error "dial_13")
                             (setq
                       		    *rtm_dinamicaX* (Cx:dinamica (get_tile "DinamicaX"))
                                    *rtm_dinamicaY* (Cx:dinamica (get_tile "DinamicaY"))
                                    *rtm_dinamicaZ* (Cx:dinamica (get_tile "DinamicaZ"))

				    *rtm_F_desloca* (Cx:fatdeslo (get_tile "Desloca"))

			            *rtm_normal_0*  (get_tile "Pts_Nor_00")
				    *rtm_normal_1*  (get_tile "Pts_Nor_01")
				    *rtm_normal_2*  (get_tile "Pts_Nor_02")
				    *rtm_normal_3*  (get_tile "Pts_Nor_03")
				    *rtm_normal_4*  (get_tile "Pts_Nor_04")
				    *rtm_normal_5*  (get_tile "Pts_Nor_05")
				    *rtm_normal_6*  (get_tile "Pts_Nor_06")
				    *rtm_normal_7*  (get_tile "Pts_Nor_07")
				    *rtm_normal_8*  (get_tile "Pts_Nor_08")
				    *rtm_normal_9*  (get_tile "Pts_Nor_09")

				    *rtm_desloca*   (get_tile "Regla_01")
                                    *rtm_modular*   (get_tile "Regla_02")
                                    *rtm_interva*   (get_tile "Regla_03")
                                    *rtm_usafreq*   (get_tile "Regla_04")
                                    *rtm_marcar*    (get_tile "Regla_05")
				    *rtm_rotari*    (get_tile "Regla_06")
				    *rtm_usaMAX*    (get_tile "Regla_07")
				    *rtm_atonal*    (get_tile "Regla_08")
				    *rtm_proges*    (get_tile "Regla_09")
                             )
  (Cx:error "dial_14")
                             (set_tile    "Pos_00"       "0") (setq *rtm_pos0*     (get_tile    "Pos_00"))
                             (set_tile    "Pos_01"       "1") (setq *rtm_pos1*     (get_tile    "Pos_01"))
                             (set_tile    "Pos_02"       "2") (setq *rtm_pos2*     (get_tile    "Pos_02"))
                             (set_tile    "Pos_03"       "3") (setq *rtm_pos3*     (get_tile    "Pos_03"))
                             (set_tile    "Pos_04"       "4") (setq *rtm_pos4*     (get_tile    "Pos_04"))
                             (set_tile    "Pos_05"       "5") (setq *rtm_pos5*     (get_tile    "Pos_05"))
                             (set_tile    "Pos_06"       "6") (setq *rtm_pos6*     (get_tile    "Pos_06"))
                             (set_tile    "Pos_07"       "7") (setq *rtm_pos7*     (get_tile    "Pos_07"))
                             (set_tile    "Pos_08"       "8") (setq *rtm_pos8*     (get_tile    "Pos_08"))
                             (set_tile    "Pos_09"       "9") (setq *rtm_pos9*     (get_tile    "Pos_09"))

                             (set_tile    "Pul_00"       "1") (setq *rtm_pul0*     (get_tile    "Pul_00"))
                             (set_tile    "Pul_01"       "1") (setq *rtm_pul1*     (get_tile    "Pul_01"))
                             (set_tile    "Pul_02"       "1") (setq *rtm_pul2*     (get_tile    "Pul_02"))
                             (set_tile    "Pul_03"       "1") (setq *rtm_pul3*     (get_tile    "Pul_03"))
                             (set_tile    "Pul_04"       "1") (setq *rtm_pul4*     (get_tile    "Pul_04"))
                             (set_tile    "Pul_05"       "1") (setq *rtm_pul5*     (get_tile    "Pul_05"))
                             (set_tile    "Pul_06"       "1") (setq *rtm_pul6*     (get_tile    "Pul_06"))
                             (set_tile    "Pul_07"       "1") (setq *rtm_pul7*     (get_tile    "Pul_07"))
                             (set_tile    "Pul_08"       "1") (setq *rtm_pul8*     (get_tile    "Pul_08"))
                             (set_tile    "Pul_09"       "1") (setq *rtm_pul9*     (get_tile    "Pul_09"))

                             (set_tile    "Per_00"       "1") (setq *rtm_Per0*     (get_tile    "Per_00"))
                             (set_tile    "Per_01"       "1") (setq *rtm_Per1*     (get_tile    "Per_01"))
                             (set_tile    "Per_02"       "1") (setq *rtm_Per2*     (get_tile    "Per_02"))
                             (set_tile    "Per_03"       "1") (setq *rtm_Per3*     (get_tile    "Per_03"))
                             (set_tile    "Per_04"       "1") (setq *rtm_Per4*     (get_tile    "Per_04"))
                             (set_tile    "Per_05"       "1") (setq *rtm_Per5*     (get_tile    "Per_05"))
                             (set_tile    "Per_06"       "1") (setq *rtm_Per6*     (get_tile    "Per_06"))
                             (set_tile    "Per_07"       "1") (setq *rtm_Per7*     (get_tile    "Per_07"))
                             (set_tile    "Per_08"       "1") (setq *rtm_Per8*     (get_tile    "Per_08"))
                             (set_tile    "Per_09"       "1") (setq *rtm_Per9*     (get_tile    "Per_09"))
  
                             (set_tile    "Rit_00"       "0") (setq *rtm_rit0*     (get_tile    "Rit_00"))
                             (set_tile    "Rit_01"       "0") (setq *rtm_rit1*     (get_tile    "Rit_01"))
                             (set_tile    "Rit_02"       "0") (setq *rtm_rit2*     (get_tile    "Rit_02"))
                             (set_tile    "Rit_03"       "0") (setq *rtm_rit3*     (get_tile    "Rit_03"))
                             (set_tile    "Rit_04"       "0") (setq *rtm_rit4*     (get_tile    "Rit_04"))
                             (set_tile    "Rit_05"       "0") (setq *rtm_rit5*     (get_tile    "Rit_05"))
                             (set_tile    "Rit_06"       "0") (setq *rtm_rit6*     (get_tile    "Rit_06"))
                             (set_tile    "Rit_07"       "0") (setq *rtm_rit7*     (get_tile    "Rit_07"))
                             (set_tile    "Rit_08"       "0") (setq *rtm_rit8*     (get_tile    "Rit_08"))
                             (set_tile    "Rit_09"       "0") (setq *rtm_rit9*     (get_tile    "Rit_09"))

                             (set_tile    "Fes_00"       "1") (setq *rtm_fes0*     (atoi (get_tile    "Fes_00")))
                             (set_tile    "Fes_01"       "1") (setq *rtm_fes1*     (atoi (get_tile    "Fes_01")))
                             (set_tile    "Fes_02"       "1") (setq *rtm_fes2*     (atoi (get_tile    "Fes_02")))
                             (set_tile    "Fes_03"       "1") (setq *rtm_fes3*     (atoi (get_tile    "Fes_03")))
                             (set_tile    "Fes_04"       "1") (setq *rtm_fes4*     (atoi (get_tile    "Fes_04")))
                             (set_tile    "Fes_05"       "1") (setq *rtm_fes5*     (atoi (get_tile    "Fes_05")))
                             (set_tile    "Fes_06"       "1") (setq *rtm_fes6*     (atoi (get_tile    "Fes_06")))
                             (set_tile    "Fes_07"       "1") (setq *rtm_fes7*     (atoi (get_tile    "Fes_07")))
                             (set_tile    "Fes_08"       "1") (setq *rtm_fes8*     (atoi (get_tile    "Fes_08")))
                             (set_tile    "Fes_09"       "1") (setq *rtm_fes9*     (atoi (get_tile    "Fes_09")))
  (Cx:error "dial_15")
                             (action_tile "OPUS"        "(setq *rtm_NomeOpus*  $value)")
                             (action_tile "UNIDADE"     "(progn (setq *rtm_unidad*  (Cx:real   $value) *rtm_unidai* *rtm_unidad*) (Cx:Unidade *rtm_unidad* nil))")
                             (action_tile "PERIODO"     "(progn (setq *rtm_periodo* (Cx:real   $value)))")
                             (action_tile "FRASE"       "(progn (setq *rtm_M_Frase* (Cx:entero $value)))")
  (Cx:error "dial_16")   
                             (action_tile "Voz_00"      "(Cx:arma_vozes  (list  (Cx:item_0  0)  (Cx:item_1  0)  $value))")
                             (action_tile "Voz_01"      "(Cx:arma_vozes  (list  (Cx:item_0  1)  (Cx:item_1  1)  $value))")
                             (action_tile "Voz_02"      "(Cx:arma_vozes  (list  (Cx:item_0  2)  (Cx:item_1  2)  $value))")
                             (action_tile "Voz_03"      "(Cx:arma_vozes  (list  (Cx:item_0  3)  (Cx:item_1  3)  $value))")
                             (action_tile "Voz_04"      "(Cx:arma_vozes  (list  (Cx:item_0  4)  (Cx:item_1  4)  $value))")
                             (action_tile "Voz_05"      "(Cx:arma_vozes  (list  (Cx:item_0  5)  (Cx:item_1  5)  $value))")
                             (action_tile "Voz_06"      "(Cx:arma_vozes  (list  (Cx:item_0  6)  (Cx:item_1  6)  $value))")
                             (action_tile "Voz_07"      "(Cx:arma_vozes  (list  (Cx:item_0  7)  (Cx:item_1  7)  $value))")
                             (action_tile "Voz_08"      "(Cx:arma_vozes  (list  (Cx:item_0  8)  (Cx:item_1  8)  $value))")
                             (action_tile "Voz_09"      "(Cx:arma_vozes  (list  (Cx:item_0  9)  (Cx:item_1  9)  $value))")
 (Cx:error "dial_17") 
                             (action_tile "Laye_Voz_00" "(Cx:arma_vozes  (list  (Cx:item_0  0)  (Cx:item_L  $value)  (Cx:item_2  0)))")
                             (action_tile "Laye_Voz_01" "(Cx:arma_vozes  (list  (Cx:item_0  1)  (Cx:item_L  $value)  (Cx:item_2  1)))")
                             (action_tile "Laye_Voz_02" "(Cx:arma_vozes  (list  (Cx:item_0  2)  (Cx:item_L  $value)  (Cx:item_2  2)))")
                             (action_tile "Laye_Voz_03" "(Cx:arma_vozes  (list  (Cx:item_0  3)  (Cx:item_L  $value)  (Cx:item_2  3)))")
                             (action_tile "Laye_Voz_04" "(Cx:arma_vozes  (list  (Cx:item_0  4)  (Cx:item_L  $value)  (Cx:item_2  4)))")
                             (action_tile "Laye_Voz_05" "(Cx:arma_vozes  (list  (Cx:item_0  5)  (Cx:item_L  $value)  (Cx:item_2  5)))")
                             (action_tile "Laye_Voz_06" "(Cx:arma_vozes  (list  (Cx:item_0  6)  (Cx:item_L  $value)  (Cx:item_2  6)))")
                             (action_tile "Laye_Voz_07" "(Cx:arma_vozes  (list  (Cx:item_0  7)  (Cx:item_L  $value)  (Cx:item_2  7)))")
                             (action_tile "Laye_Voz_08" "(Cx:arma_vozes  (list  (Cx:item_0  8)  (Cx:item_L  $value)  (Cx:item_2  8)))")
                             (action_tile "Laye_Voz_09" "(Cx:arma_vozes  (list  (Cx:item_0  9)  (Cx:item_L  $value)  (Cx:item_2  9)))")
 (Cx:error "dial_18") 
                             (action_tile "Inst_Voz_00" "(Cx:arma_instr  \"0\"  $value))")
                             (action_tile "Inst_Voz_01" "(Cx:arma_instr  \"1\"  $value))")
                             (action_tile "Inst_Voz_02" "(Cx:arma_instr  \"2\"  $value))")
                             (action_tile "Inst_Voz_03" "(Cx:arma_instr  \"3\"  $value))")
                             (action_tile "Inst_Voz_04" "(Cx:arma_instr  \"4\"  $value))")
                             (action_tile "Inst_Voz_05" "(Cx:arma_instr  \"5\"  $value))")
                             (action_tile "Inst_Voz_06" "(Cx:arma_instr  \"6\"  $value))")
                             (action_tile "Inst_Voz_07" "(Cx:arma_instr  \"7\"  $value))")
                             (action_tile "Inst_Voz_08" "(Cx:arma_instr  \"8\"  $value))")
                             (action_tile "Inst_Voz_09" "(Cx:arma_instr  \"9\"  $value))")
 (Cx:error "dial_19") 
                             (action_tile "Modo_Voz_00" "(setq *rtm_escala_0* (Cx:pega_escala $value) *rtm_escala_0_txt* (Cx:pega_escala_txt  $value))")
                             (action_tile "Modo_Voz_01" "(setq *rtm_escala_1* (Cx:pega_escala $value) *rtm_escala_1_txt* (Cx:pega_escala_txt  $value))")
                             (action_tile "Modo_Voz_02" "(setq *rtm_escala_2* (Cx:pega_escala $value) *rtm_escala_2_txt* (Cx:pega_escala_txt  $value))")
                             (action_tile "Modo_Voz_03" "(setq *rtm_escala_3* (Cx:pega_escala $value) *rtm_escala_3_txt* (Cx:pega_escala_txt  $value))")
                             (action_tile "Modo_Voz_04" "(setq *rtm_escala_4* (Cx:pega_escala $value) *rtm_escala_4_txt* (Cx:pega_escala_txt  $value))")
                             (action_tile "Modo_Voz_05" "(setq *rtm_escala_5* (Cx:pega_escala $value) *rtm_escala_5_txt* (Cx:pega_escala_txt  $value))")
                             (action_tile "Modo_Voz_06" "(setq *rtm_escala_6* (Cx:pega_escala $value) *rtm_escala_6_txt* (Cx:pega_escala_txt  $value))")
                             (action_tile "Modo_Voz_07" "(setq *rtm_escala_7* (Cx:pega_escala $value) *rtm_escala_7_txt* (Cx:pega_escala_txt  $value))")
                             (action_tile "Modo_Voz_08" "(setq *rtm_escala_8* (Cx:pega_escala $value) *rtm_escala_8_txt* (Cx:pega_escala_txt  $value))")
                             (action_tile "Modo_Voz_09" "(setq *rtm_escala_9* (Cx:pega_escala $value) *rtm_escala_9_txt* (Cx:pega_escala_txt  $value))")   
 (Cx:error "dial_20") 
                             (action_tile "Temp_Voz_00" "(Cx:Modulo_da_voz  0  $value)")
                             (action_tile "Temp_Voz_01" "(Cx:Modulo_da_voz  1  $value)")
                             (action_tile "Temp_Voz_02" "(Cx:Modulo_da_voz  2  $value)")
                             (action_tile "Temp_Voz_03" "(Cx:Modulo_da_voz  3  $value)")
                             (action_tile "Temp_Voz_04" "(Cx:Modulo_da_voz  4  $value)")
                             (action_tile "Temp_Voz_05" "(Cx:Modulo_da_voz  5  $value)")
                             (action_tile "Temp_Voz_06" "(Cx:Modulo_da_voz  6  $value)")
                             (action_tile "Temp_Voz_07" "(Cx:Modulo_da_voz  7  $value)")
                             (action_tile "Temp_Voz_08" "(Cx:Modulo_da_voz  8  $value)")
                             (action_tile "Temp_Voz_09" "(Cx:Modulo_da_voz  9  $value)") 
 (Cx:error "dial_21")                                
                             (action_tile "Meto_Voz_00" "(Cx:Metodo_da_voz  0  $value)")
                             (action_tile "Meto_Voz_01" "(Cx:Metodo_da_voz  1  $value)")
                             (action_tile "Meto_Voz_02" "(Cx:Metodo_da_voz  2  $value)")
                             (action_tile "Meto_Voz_03" "(Cx:Metodo_da_voz  3  $value)")
                             (action_tile "Meto_Voz_04" "(Cx:Metodo_da_voz  4  $value)")
                             (action_tile "Meto_Voz_05" "(Cx:Metodo_da_voz  5  $value)")
                             (action_tile "Meto_Voz_06" "(Cx:Metodo_da_voz  6  $value)")
                             (action_tile "Meto_Voz_07" "(Cx:Metodo_da_voz  7  $value)")
                             (action_tile "Meto_Voz_08" "(Cx:Metodo_da_voz  8  $value)")
                             (action_tile "Meto_Voz_09" "(Cx:Metodo_da_voz  9  $value)")
 (Cx:error "dial_22")
                             (action_tile "Pts_Nor_00"  "(Cx:normal         0  $value)")
                             (action_tile "Pts_Nor_01"  "(Cx:normal         1  $value)")
                             (action_tile "Pts_Nor_02"  "(Cx:normal         2  $value)")
                             (action_tile "Pts_Nor_03"  "(Cx:normal         3  $value)")
                             (action_tile "Pts_Nor_04"  "(Cx:normal         4  $value)")
                             (action_tile "Pts_Nor_05"  "(Cx:normal         5  $value)")
                             (action_tile "Pts_Nor_06"  "(Cx:normal         6  $value)")
                             (action_tile "Pts_Nor_07"  "(Cx:normal         7  $value)")  
                             (action_tile "Pts_Nor_08"  "(Cx:normal         8  $value)")
                             (action_tile "Pts_Nor_09"  "(Cx:normal         9  $value)")
 (Cx:error "dial_23")
                             (action_tile "Pos_00"      "(setq  *rtm_pos0* $value)")
                             (action_tile "Pos_01"      "(setq  *rtm_pos1* $value)")
                             (action_tile "Pos_02"      "(setq  *rtm_pos2* $value)")
                             (action_tile "Pos_03"      "(setq  *rtm_pos3* $value)")
                             (action_tile "Pos_04"      "(setq  *rtm_pos4* $value)")
                             (action_tile "Pos_05"      "(setq  *rtm_pos5* $value)")
                             (action_tile "Pos_06"      "(setq  *rtm_pos6* $value)")
                             (action_tile "Pos_07"      "(setq  *rtm_pos7* $value)")
                             (action_tile "Pos_08"      "(setq  *rtm_pos8* $value)")
                             (action_tile "Pos_09"      "(setq  *rtm_pos9* $value)")

                             (action_tile "Pul_00"      "(setq  *rtm_pul0* $value)")
                             (action_tile "Pul_01"      "(setq  *rtm_pul1* $value)")
                             (action_tile "Pul_02"      "(setq  *rtm_pul2* $value)")
                             (action_tile "Pul_03"      "(setq  *rtm_pul3* $value)")
                             (action_tile "Pul_04"      "(setq  *rtm_pul4* $value)")
                             (action_tile "Pul_05"      "(setq  *rtm_pul5* $value)")
                             (action_tile "Pul_06"      "(setq  *rtm_pul6* $value)")
                             (action_tile "Pul_07"      "(setq  *rtm_pul7* $value)")
                             (action_tile "Pul_08"      "(setq  *rtm_pul8* $value)")
                             (action_tile "Pul_09"      "(setq  *rtm_pul9* $value)")

                             (action_tile "Per_00"      "(setq  *rtm_Per0* $value)")
                             (action_tile "Per_01"      "(setq  *rtm_Per1* $value)")
                             (action_tile "Per_02"      "(setq  *rtm_Per2* $value)")
                             (action_tile "Per_03"      "(setq  *rtm_Per3* $value)")
                             (action_tile "Per_04"      "(setq  *rtm_Per4* $value)")
                             (action_tile "Per_05"      "(setq  *rtm_Per5* $value)")
                             (action_tile "Per_06"      "(setq  *rtm_Per6* $value)")
                             (action_tile "Per_07"      "(setq  *rtm_Per7* $value)")
                             (action_tile "Per_08"      "(setq  *rtm_Per8* $value)")
                             (action_tile "Per_09"      "(setq  *rtm_Per9* $value)")
  
                             (action_tile "Rit_00"      "(setq  *rtm_rit0* $value)")
                             (action_tile "Rit_01"      "(setq  *rtm_rit1* $value)")
                             (action_tile "Rit_02"      "(setq  *rtm_rit2* $value)")
                             (action_tile "Rit_03"      "(setq  *rtm_rit3* $value)")
                             (action_tile "Rit_04"      "(setq  *rtm_rit4* $value)")
                             (action_tile "Rit_05"      "(setq  *rtm_rit5* $value)")
                             (action_tile "Rit_06"      "(setq  *rtm_rit6* $value)")
                             (action_tile "Rit_07"      "(setq  *rtm_rit7* $value)")
                             (action_tile "Rit_08"      "(setq  *rtm_rit8* $value)")
                             (action_tile "Rit_09"      "(setq  *rtm_rit9* $value)")

                             (action_tile "Fes_00"      "(setq  *rtm_fes0* (atoi $value))")
                             (action_tile "Fes_01"      "(setq  *rtm_fes1* (atoi $value))")
                             (action_tile "Fes_02"      "(setq  *rtm_fes2* (atoi $value))")
                             (action_tile "Fes_03"      "(setq  *rtm_fes3* (atoi $value))")
                             (action_tile "Fes_04"      "(setq  *rtm_fes4* (atoi $value))")
                             (action_tile "Fes_05"      "(setq  *rtm_fes5* (atoi $value))")
                             (action_tile "Fes_06"      "(setq  *rtm_fes6* (atoi $value))")
                             (action_tile "Fes_07"      "(setq  *rtm_fes7* (atoi $value))")
                             (action_tile "Fes_08"      "(setq  *rtm_fes8* (atoi $value))")
                             (action_tile "Fes_09"      "(setq  *rtm_fes9* (atoi $value))")
 (Cx:error "dial_24")
                             (action_tile "Regla_01"    "(setq *rtm_desloca* $value)")
                             (action_tile "Regla_02"    "(setq *rtm_modular* $value)")
                             (action_tile "Regla_03"    "(setq *rtm_interva* $value)")
                             (action_tile "Regla_04"    "(setq *rtm_usafreq* $value)")
                             (action_tile "Regla_05"    "(setq *rtm_marcar*  $value)")  
                             (action_tile "Regla_06"    "(setq *rtm_rotari*  $value)")
                             (action_tile "Regla_07"    "(setq *rtm_usaMAX*  $value)")
                             (action_tile "Regla_08"    "(setq *rtm_atonal*  $value)")
                             (action_tile "Regla_09"    "(setq *rtm_proges*  $value)")
 (Cx:error "dial_25") 
                             (action_tile "Desloca"     "(setq *rtm_F_desloca* (Cx:fatdeslo $value))")
  
                             (action_tile "DinamicaX"   "(setq *rtm_dinamicaX* (Cx:dinamica $value))")
                             (action_tile "DinamicaY"   "(setq *rtm_dinamicaY* (Cx:dinamica $value))")
                             (action_tile "DinamicaZ"   "(setq *rtm_dinamicaZ* (Cx:dinamica $value))")

                             (action_tile "PULSOS"      "(progn (setq *rtm_pulsos* $value) (set_tile \"TXTPULSOS\" $value))")

                             (action_tile "accept"      "(progn (setq *rtm_accion* 1 cancelar 0) (done_dialog))")
                             (action_tile "cancel"      "(progn (setq *rtm_accion* 0 cancelar 1) (done_dialog))")
 (Cx:error "dial_26")
                             (start_dialog)
                             (done_dialog)
                             (unload_dialog qdialogo)
)

(defun Cx:pega_escala (#e)
                             (if (Cx:dodecafonica?)
                                 *rtm_serie12*
                                 (cadr (nth (atoi #e) *rtm_escalas*))
                             )
)

(defun Cx:pega_escala_txt (#e)
                             (if (Cx:dodecafonica?)
                                 "Serie12*"
                                 (car (nth (atoi #e) *rtm_escalas*))
                             )
)

(defun Cx:dinamica (#d)      (* (atof #d) 0.10))
(defun Cx:fatdeslo (#d)      (atof #d))

(defun Cx:Modulo_da_voz (#v #i)
                                   (set        (read (strcat "*tempo_Voz_0" (itoa #v) "*")) (cadr   (nth (atoi #i) *rtm_tempo_vozes*)))
                                   (set        (read (strcat "*veloc_Voz_0" (itoa #v) "*")) (caddr  (nth (atoi #i) *rtm_tempo_vozes*)))
                                   (set        (read (strcat "*retro_Voz_0" (itoa #v) "*")) (cadddr (nth (atoi #i) *rtm_tempo_vozes*)))
)

(defun Cx:Metodo_da_voz (#v #i)    (set        (read (strcat "*metodo_Voz_0" (itoa #v) "*"))  #i))

(defun Cx:eval_dur_Voz (#v)        (eval (read (strcat "*tempo_Voz_0"  #v "*"))))
(defun Cx:eval_vel_Voz (#v)        (eval (read (strcat "*veloc_Voz_0"  #v "*"))))
(defun Cx:eval_dir_Voz (#v)        (eval (read (strcat "*retro_Voz_0"  #v "*"))))
(defun Cx:eval_met_Voz (#v)        (eval (read (strcat "*metodo_Voz_0" #v "*"))))
(defun Cx:eval_pul_Voz (#v)        (eval (read (strcat "*rtm_pul"      #v "*"))))
(defun Cx:eval_per_Voz (#v)        (eval (read (strcat "*rtm_per"      #v "*"))))
(defun Cx:eval_rit_Voz (#v)        (eval (read (strcat "*rtm_rit"      #v "*"))))
(defun Cx:eval_fes_Voz (#v)        (eval (read (strcat "*rtm_fes"      #v "*"))))

(defun Cx:campos       (#lstvar #lsttil #lstval)
                                (mapcar
			               '(lambda (var til val)
			                        (cond
						     ((= (eval var) nil)
						                       (cond
								            ((Cx:real?   var)  (set var  (atof val)))
								            ((Cx:entero? var)  (set var  (atoi val)))
								            (t                 (set var        val))
								       )     
				 	                               (set_tile til val)
						     )
                                                     (t               (cond
									   ((Cx:real?   var)  (set_tile til (rtos (eval var)  2 2)))
									   ((Cx:entero? var)  (set_tile til (itoa (eval var))))
									   (t                 (set_tile til       (eval var)))
								      )
						     )
	                    	                ) 
			               )
			                #lstvar
			                #lsttil
			                #lstval
                                )
) 

(defun Cx:item_0 (#n)          (nth 0  (nth  #n  *rtm_O_vozes*)))
(defun Cx:item_1 (#n)          (nth 1  (nth  #n  *rtm_O_vozes*)))
(defun Cx:item_2 (#n)          (nth 2  (nth  #n  *rtm_O_vozes*)))

(defun Cx:item_L (#n)          (nth          (atoi #n)  *rtm_O_layers*))

(defun Cx:normal (#r #v)       (set (read (strcat "*rtm_normal_" (itoa #r) "*")) #v))


(defun Cx:lista_orq (#n)
    (nth #n
      (list
	'(     "Voz_00"       "Voz_01"       "Voz_02"       "Voz_03"       "Voz_04"       "Voz_05"       "Voz_06"       "Voz_07"       "Voz_08"       "Voz_09")
        '("Laye_Voz_00"  "Laye_Voz_01"  "Laye_Voz_02"  "Laye_Voz_03"  "Laye_Voz_04"  "Laye_Voz_05"  "Laye_Voz_06"  "Laye_Voz_07"  "Laye_Voz_08"  "Laye_Voz_09")
        '("Inst_Voz_00"  "Inst_Voz_01"  "Inst_Voz_02"  "Inst_Voz_03"  "Inst_Voz_04"  "Inst_Voz_05"  "Inst_Voz_06"  "Inst_Voz_07"  "Inst_Voz_08"  "Inst_Voz_09")
	'("Modo_Voz_00"  "Modo_Voz_01"  "Modo_Voz_02"  "Modo_Voz_03"  "Modo_Voz_04"  "Modo_Voz_05"  "Modo_Voz_06"  "Modo_Voz_07"  "Modo_Voz_08"  "Modo_Voz_09")
	'("Temp_Voz_00"  "Temp_Voz_01"  "Temp_Voz_02"  "Temp_Voz_03"  "Temp_Voz_04"  "Temp_Voz_05"  "Temp_Voz_06"  "Temp_Voz_07"  "Temp_Voz_08"  "Temp_Voz_09")
	'("Meto_Voz_00"  "Meto_Voz_01"  "Meto_Voz_02"  "Meto_Voz_03"  "Meto_Voz_04"  "Meto_Voz_05"  "Meto_Voz_06"  "Meto_Voz_07"  "Meto_Voz_08"  "Meto_Voz_09")
      )
     )
)


(defun Cx:metodos ()
                     (setq *rtm_metodos* '(
					   "Morfologia_S"
					   "Morfologia_T"
					   "Trama P.Inteiro"
					   "Trama P.Metade" 
                                           "Trama P.Quarto" 
                                           "Trama P.Oitavo"
					   "Multiplos_21"
					   "Multiplos_321"
					   "Multiplos_4321"					   
					   "Multiplos_54321"
					   "Multiplos_1054321"
					   "Pontos_faces"
					   "Pontos_01"
					   "Centros"
					   "Coordenada->frequencia"
                                          )
	             )
)

(defun Cx:activa_vozes (#l)
                               (setq nvox 1)
                               (mapcar '(lambda (v)
			  	                (if (<= nvox (length  #l))
                                                    (set_tile  v  "1")
					            (progn
						         (mode_tile v                   0)
						         (mode_tile (strcat "Laye_" v)  0)
						         (mode_tile (strcat "Inst_" v)  0)
						    )  
					        )
					        (setq nvox (1+ nvox))
					)
					(Cx:lista_orq 0))
)

(defun Cx:activa_Layers  (#l)  (mapcar '(lambda (v) (Cx:activa_lst v              #l))  (Cx:lista_orq 1)))
(defun Cx:activa_coro    (#l)  (mapcar '(lambda (v) (Cx:activa_lst v (mapcar 'car #l))) (Cx:lista_orq 2)))
(defun Cx:activa_escala  (#l)  (mapcar '(lambda (v) (Cx:activa_lst v (mapcar 'car #l))) (Cx:lista_orq 3)) (Cx:escala_U (car (nth 0 *rtm_escalas*))))
(defun Cx:activa_Tempos  (#l)  (mapcar '(lambda (v) (Cx:activa_lst v (mapcar 'car #l))) (Cx:lista_orq 4)))
(defun Cx:activa_Metodos (#l)  (mapcar '(lambda (v) (Cx:activa_lst v              #l))  (Cx:lista_orq 5)))

(defun Cx:arma_instr (#i #novo)
                               (setq instrumento_selec (Cx:instrumento #novo))
  
                               (setq *rtm_L_programa*  (subst (list #i
                                                                   (nth 1 instrumento_selec)
			                                           (nth 3 instrumento_selec)
			                                           (nth 4 instrumento_selec)
			                                     ) 
                                                             (assoc #i  *rtm_L_programa*)
				                             *rtm_L_programa*
					               )
			             *rtm_A_programa*  (subst (list #i
                                                                   (nth 2 instrumento_selec)
			                                           (nth 3 instrumento_selec)
			                                           (nth 4 instrumento_selec)
			                                     ) 
                                                             (assoc  #i  *rtm_A_programa*)
				                             *rtm_A_programa*
					               )
				    )
)
  
(defun Cx:instrumento (#novo) (nth (atoi #novo) *rtm_L_instru*))

(defun Cx:arma_vozes (#l)     (setq *rtm_O_vozes* (subst
						        (list   (nth 0 #l) (nth 1 #l) (nth 2 #l)) 
                                                        (assoc  (nth 0 #l) *rtm_O_vozes*)
				                        *rtm_O_vozes*
						  )
			      )
)
 
(defun Cx:activa_lst (#t #l) (start_list #t) (mapcar 'add_list #l) (end_list))
